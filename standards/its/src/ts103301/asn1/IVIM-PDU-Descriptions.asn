--! @options: no-fields-header

IVIM-PDU-Descriptions {
    itu-t (0) identified-organization (4) etsi (0) itsDomain (5) wg1 (1) ts103301 (103301) ivim (2) major-version-2 (2) minor-version-1 (1)
}

DEFINITIONS AUTOMATIC TAGS ::=

BEGIN

IMPORTS

IviStructure
FROM IVI {
  iso (1) standard (0) ivi (19321) major-version-3 (3) minor-version-1 (1)
}
WITH SUCCESSORS

ItsPduHeader
FROM ETSI-ITS-CDD {
  itu-t (0) identified-organization (4) etsi (0) itsDomain (5) wg1 (1) 102894 cdd (2) major-version-4 (4) minor-version-1 (1)
}
WITH SUCCESSORS;

/**
* In vehicle information Message Message
* This DF includes DEs for the IVIM protocolVersion, the IVI message type identifier `messageID`,
* the station identifier `stationID` of the originating ITS-S and the IVI data from ISO TS 19321.
*
* @field header: The DE `protocolVersion` is used to select the appropriate protocol decoder at the receiving ITS-S. 
*                It shall be set to 2.
*                The DE `messageID` shall be ivim(6).
* @field ivi:    contains the IVI data as defined in ISO TS 19321.
* 
* @category: Basic Information
* @revision: V1.3.1
*/
IVIM ::= SEQUENCE {
    header  ItsPduHeader,
    ivi     IviStructure
}

END
