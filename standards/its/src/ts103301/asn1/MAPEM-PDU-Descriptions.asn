--! @options: no-fields-header

MAPEM-PDU-Descriptions {
    itu-t (0) identified-organization (4) etsi (0) itsDomain (5) wg1 (1) ts103301 (103301) mapem (1) version2 (2)
}

DEFINITIONS AUTOMATIC TAGS ::=

BEGIN

IMPORTS

/**
* Includes from ETSI-ITS-DSRC
*/
MapData
FROM ETSI-ITS-DSRC {
  itu-t (0) identified-organization (4) etsi (0) itsDomain (5) wg1 (1) ts103301 (103301) dsrc (6) major-version-2 (2) minor-version-1 (1)
}
WITH SUCCESSORS

/**
* Include ETSI TS 102 894-2 (ETSI-ITS-CDD)
*/
ItsPduHeader
FROM ETSI-ITS-CDD {
  itu-t (0) identified-organization (4) etsi (0) itsDomain (5) wg1 (1) 102894 cdd (2) major-version-4 (4) minor-version-1 (1)
}
WITH SUCCESSORS;

/**
* Map (lane topology) extended Message
* This DF includes DEs for the MAPEM: protocolVersion, the MAPEM message type identifier `messageID`, 
* the station identifier `stationID` of the originating ITS-S and the Map data from ETSI-ITS-DSRC.
* 
* @field header:  The DE `protocolVersion` is used to select the appropriate protocol decoder at the receiving ITS-S. 
*                 It shall be set to 2.
*                 The DE `messageID` shall be mapem(5).
* @field map:     contains the MAP data as defined in ETSI-ITS-DSRC.
* 
* @category: Basic Information
* @revision: V1.3.1
*/
MAPEM ::= SEQUENCE {
    header  ItsPduHeader,
    map	    MapData
}

END
